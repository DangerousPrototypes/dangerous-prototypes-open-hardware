#usage "exports the library as an script, chop it into (managable) pieces"

// Written by Chris van Dongen for Dangerous Prototypes

// copied MakeValidFileName from lbr-dump-common.inc written by Francesco Montorsi <frm@users.sourceforge.net>

string MakeValidFileName(string fn)
{
    string inv_chars = "/\\:?*\"<>|";
    
    string ret;
    int x;
    for (x=0; x<strlen(fn); x++)
        if (strchr(inv_chars, fn[x]) == -1)
            ret = ret + fn[x];      // fn[x] is not in the inv_chars string
        else
            ret = ret + "_";        // fn[x] is an invalid char; replace it with an underscore
    
    return ret;
}

// Main starts here
// vars
string path, fname, fname2;		
int i, j, stop, found;
string part;
int nLines, stdlines;
int startc, stopc;
string lines[];
string files[];
string notadded="Skipped:";
string added="Added:";
int numFiles;

// some info :)
dlgMessageBox("!This  script will take an export>script from a library and splits it into small scripts. This will (hopefully) prevent overwritting parts other people added and help the svn to track. If a small script already exist it will not be exported!!!");

// ask user for script
fname = dlgFileOpen("Select the library.scr", "", "*.scr");
path = filedir(fname);

// read scripts in directory
numFiles=fileglob(files, path + "*.scr");

// clears any fileerrors
fileerror();

// read in the file
nLines=fileread(lines, fname);

// if not found quit
if(fileerror())
{	exit(1);
}

// the first few lines are standard settings (i.e. layernames and grid)
// and save them
stdlines=0;
while(lines[stdlines]!="")
{	stdlines++;
}
stdlines++;
i=stdlines;


// construct librarydefaults script
sprintf(fname2, "%s%s", path, "librarydefaults.scr");
output(fname2, "wt")
{	printf("# Autogenerated by lbrdump.ulp use lbrbuild.ulp to reconstruct library\n");
	printf("# \n");
	printf("# more info about the script: http://dangerousprototypes.com/docs/Dangerous_Prototypes_Cadsoft_Eagle_parts_library \n");
	printf("# \n");
	printf("\n");

	for(j=0; j<stdlines; j++)
	{	if(lines[j][0]!='#') printf("%s\n", lines[j]);
	}

}


// loop untill the end, spit out each device, symbol, and package
while(!stop)
{	// derive the partname
	startc=strchr(lines[i], '\'');
	stopc=strchr(lines[i], '\'', startc+1);
	part=strsub(lines[i], startc+1, (stopc-startc)-1);

	// construct filename
	sprintf(fname, "%s%s.scr", path, MakeValidFileName(part));
	status(fname);

	// Check if already exist
	for(j=0; j<numFiles; j++)
	{	if(strstr(files[j], MakeValidFileName(part))!=-1)
		{	found=1;
			j=numFiles+1;
		}
	}


	// write file if not found
	if(found)
	{	sprintf(notadded, "%s %s", notadded, part);

		while(lines[i]!="") i++;
	}
	else
	{	sprintf(added, "%s %s", added, part);
		output(fname, "wt") 
		{	// TODO: add DP header with license
			printf("# Autogenerated by lbrdump.ulp use lbrbuild.ulp to reconstruct library\n");
			printf("# \n");
			printf("# more info about the script: http://dangerousprototypes.com/docs/Dangerous_Prototypes_Cadsoft_Eagle_parts_library \n");
			printf("# \n");
			printf("\n");


			// output standard lines (without comments/layer/description)
			for(j=0; j<stdlines; j++)
			{	//if((lines[j][0]!='#')&&(strstr(lines[j], "Layer")==-1)&&(strstr(lines[j], "Description")==-1)) printf("%s\n", lines[j]);
				if((strstr(lines[j], "Set")==0)||(strstr(lines[j], "Grid")==0)) printf("%s\n", lines[j]);
			}

			printf("\n");

			// output device, symbol, or package
			while(lines[i]!="")
			{	printf("%s\n", lines[i]);
				i++;
			}
		}
	}
	i++;
	found=0;
	if(i>=nLines)	stop=1;
}

// display the ones we (didn't) add
if(notadded!="Skipped:") dlgMessageBox(notadded);
if(added!="Added:") dlgMessageBox(added);

// thank you for flying DP airlines..
exit(0);
